"""
BatteryPackLayoutTool_v3.FCMacro
=================================
FreeCAD macro for arranging battery cells inside a given geometry and
generating a wiring layout.

This file is the *thin* entry point.  All logic lives in the ``cellpacker``
package, which must be on ``sys.path`` (place it next to this macro, or
add it to FreeCAD's macro search path).

Usage
-----
1. Draw a closed sketch representing the usable pack boundary.
2. Select the sketch.  Optionally also Ctrl-select a straight edge to
   align the hex grid to a specific direction.
3. Run this macro.
"""

import sys
import os

# ── Ensure the cellpacker package is importable ────────────────────────────
_macro_dir = os.path.dirname(os.path.abspath(__file__))
if _macro_dir not in sys.path:
    sys.path.insert(0, _macro_dir)

# ── Flush any cached cellpacker modules so edits take effect immediately ───
for _mod in [k for k in sys.modules if k == "cellpacker" or k.startswith("cellpacker.")]:
    del sys.modules[_mod]

# ── Imports ────────────────────────────────────────────────────────────────
import FreeCAD as App
import FreeCADGui as Gui

from cellpacker.defaults import load_defaults
from cellpacker.utils import parse_float_list, ensure_active_doc
from cellpacker.ui.dialog import get_user_settings
from cellpacker.ui.selection import get_selected_sketch_and_edge
from cellpacker.geometry.face import get_local_face
from cellpacker.geometry.grid import grid_params_from_config, generate_candidates_from_edge
from cellpacker.geometry.transforms import get_edge_angle_in_local_coords, get_edge_local_endpoints
from cellpacker.layout.sweep import sweep_for_candidates
from cellpacker.layout.serpentine import serpentine_solutions, FAILURE_MESSAGES
from cellpacker.layout.architect import architecture_solutions, OPPOSITE
from cellpacker.geometry.layers import build_layers
from cellpacker.layout.selector import build_selected_by_series
from cellpacker.drawing.cells import (
    make_or_get_group,
    build_pack_groups,
    build_series_groups,
    draw_candidate_cells,
    draw_all_selected_cells,
    get_sketch_normal,
    _delete_tree,
)
from cellpacker.drawing.annotations import (
    draw_polarity_markers,
    draw_pack_terminals,
    draw_alignment_arrow,
)
from cellpacker.routing.busbars import draw_parallel_busbars, draw_series_busbars


# ── Main ───────────────────────────────────────────────────────────────────

def run() -> None:
    print("BatteryPackLayoutTool v3 — cellpacker loaded from:", __import__("cellpacker").__file__)
    doc = ensure_active_doc()

    # ── Selection + geometry (done once, shared by preview and final draw) ──
    sketch_obj, alignment_edge = get_selected_sketch_and_edge()
    face          = get_local_face(sketch_obj)
    bbox          = face.BoundBox
    rotation      = sketch_obj.Placement.Rotation
    sketch_normal = get_sketch_normal(sketch_obj)

    # ── Shared compute state (mutated by nested closures) ────────────────
    _state: dict = {
        "cfg":        None,  # last cfg used for compute
        "params":     None,  # grid params
        "points":     [],    # candidate cell positions
        "grid_angle": 0.0,
        "solutions":  [],    # list[dict] sorted best→worst
        "idx":        0,     # currently displayed solution index
        "last_root":  [],    # [name] of last FreeCAD group, for cleanup
    }

    # ── Render one specific solution ──────────────────────────────────────

    def _render(cfg: dict, solution: dict) -> None:
        """Draw *solution* into FreeCAD using the precomputed _state."""
        params = _state["params"]
        points = _state["points"]

        print("─" * 50)
        print(f"Grid angle      : {_state['grid_angle']:.2f}°")
        print(f"Candidate cells : {len(points)}")
        print(f"Selected        : {solution['selected_count']} / "
              f"{cfg['target_s'] * cfg['target_p']}"
              f"  (layout {_state['idx'] + 1} of {len(_state['solutions'])})")
        if solution.get("arch_info"):
            print(f"Architecture    : {solution['arch_info']}")
        if solution["failure"]:
            print(f"WARNING: {FAILURE_MESSAGES.get(solution['failure'], solution['failure'])}")
        if solution["selected"]:
            am = solution["minus_achieved"]
            ap = solution["plus_achieved"]
            tm = cfg.get("pack_minus_target", "bottom-left")
            tp = cfg.get("pack_plus_target",  "top-right")
            print(f"PACK−  target: {tm:12s}  {'✓' if am == tm else '→ achieved: ' + am}")
            print(f"PACK+  target: {tp:12s}  {'✓' if ap == tp else '→ achieved: ' + ap}")
            if solution["jumps"]:
                print(f"Jumps at series steps: {solution['jumps']}")
        print("─" * 50)

        new_root = f"BatteryPack_{cfg['target_s']}s{cfg['target_p']}p"
        last = _state["last_root"]
        if last and last[0] != new_root:
            _delete_tree(doc, last[0])
        last.clear()
        last.append(new_root)

        groups = build_pack_groups(doc, new_root)

        if cfg.get("show_candidates", True):
            try:
                groups["root"].addObject(groups["all_candidates"])
            except Exception:
                pass
            draw_candidate_cells(doc, sketch_obj, points,
                                 params.radius, rotation,
                                 groups["all_candidates"], cfg)
            if not cfg.get("candidates_visible", True):
                try:
                    groups["all_candidates"].ViewObject.Visibility = False
                except Exception:
                    pass

        if cfg["draw_alignment_arrow"]:
            draw_alignment_arrow(doc, sketch_obj, _state["grid_angle"],
                                 "PackDirection", groups["direction"],
                                 cfg["alignment_arrow_length"])

        series_groups = build_series_groups(
            doc, new_root,
            solution.get("achieved_s") or cfg["target_s"],
            groups["selected"])
        selected_by_series = build_selected_by_series(solution["selected"])

        if not selected_by_series:
            print("BatteryPackLayoutTool: no valid cell window found.")
            return

        terminal_lookup = draw_all_selected_cells(
            doc, sketch_obj, selected_by_series,
            params.radius, rotation, series_groups, cfg)

        draw_polarity_markers(doc, terminal_lookup, groups["polarity"], cfg, sketch_normal)

        if cfg.get("draw_pack_terminal_labels", True):
            draw_pack_terminals(doc, selected_by_series, terminal_lookup,
                                groups["polarity"], cfg, sketch_normal)

        if cfg["draw_busbars"]:
            draw_parallel_busbars(doc, selected_by_series, terminal_lookup,
                                  groups["busbars"], new_root, cfg, sketch_normal)
            draw_series_busbars(doc, selected_by_series, terminal_lookup,
                                groups["busbars"], new_root, cfg, sketch_normal)

        doc.recompute()

    # ── Full recompute (called by Preview) ────────────────────────────────

    def _draw(cfg: dict) -> None:
        """Recompute candidates + solutions, then render solution 0."""
        cfg = {**cfg, **build_layers(cfg)}
        params = grid_params_from_config(cfg)

        if cfg["use_selected_edge_alignment"] and alignment_edge is not None:
            p1_local, p2_local = get_edge_local_endpoints(sketch_obj, alignment_edge)
            grid_angle = get_edge_angle_in_local_coords(
                sketch_obj, alignment_edge,
                fallback_angle_deg=cfg["fallback_angle_deg"],
            )
            print(f"BatteryPackLayoutTool: edge angle = {grid_angle:.2f}° — edge-anchored grid")
            points = generate_candidates_from_edge(face, p1_local, p2_local, params)
        else:
            angle_list = parse_float_list(cfg["angles_deg"], [0, 5, 10, 15, 20, 25, 30])
            grid_angle, points = sweep_for_candidates(face, bbox, angle_list, params)
            print(f"BatteryPackLayoutTool: sweep best angle = {grid_angle:.2f}°")

        # Derive legacy PACK−/PACK+ corner targets from the architecture
        # terms (used by the adaptive fallback and the nav-bar display).
        t_side = cfg.get("terminal_side", "left")
        t_ends = cfg.get("terminal_ends", "auto")
        cfg["pack_minus_target"] = t_side
        cfg["pack_plus_target"]  = (t_side if t_ends == "same_end"
                                    else OPPOSITE.get(t_side, t_side))

        # ── Architecture-first: place the ideal pack as specified ─────────
        solutions = architecture_solutions(
            points,
            params.pitch_y,
            grid_angle,
            cfg["target_s"], cfg["target_p"],
            group_shape=cfg.get("group_shape", "auto"),
            series_path=cfg.get("series_path", "auto"),
            terminal_ends=t_ends,
            terminal_side=t_side,
            pack_position=cfg.get("pack_position", "anywhere"),
            bbox=bbox,
            top_n=5,
            priority=cfg.get("layout_priority", "group_quality"),
            degrade_mode=cfg.get("degrade_mode", "keep_p"),
        )
        if solutions:
            print(f"BatteryPackLayoutTool: architecture placed — "
                  f"{solutions[0].get('arch_info', '')}")
        else:
            # ── Fallback: adaptive serpentine search ──────────────────────
            print("BatteryPackLayoutTool: requested architecture does not "
                  "fit — using adaptive search")
            solutions = serpentine_solutions(
                points,
                params.pitch_y,
                grid_angle,
                cfg["target_s"], cfg["target_p"],
                cfg["pack_minus_target"],
                cfg["pack_plus_target"],
                bbox,
                top_n=5,
                priority=cfg.get("layout_priority", "group_quality"),
                degrade_mode=cfg.get("degrade_mode", "keep_p"),
            )

        _state["cfg"]        = cfg
        _state["params"]     = params
        _state["points"]     = points
        _state["grid_angle"] = grid_angle
        _state["solutions"]  = solutions
        _state["idx"]        = 0

        print(f"BatteryPackLayoutTool: {len(solutions)} distinct layout(s) found")
        _render(cfg, solutions[0])

    # ── Navigation (no recompute — just switch between stored solutions) ──

    def _prev() -> None:
        if _state["solutions"] and _state["idx"] > 0:
            _state["idx"] -= 1
            _render(_state["cfg"], _state["solutions"][_state["idx"]])

    def _next() -> None:
        sols = _state["solutions"]
        if sols and _state["idx"] < len(sols) - 1:
            _state["idx"] += 1
            _render(_state["cfg"], _state["solutions"][_state["idx"]])

    def _nav_info() -> tuple:
        """Return (current_1based, total, info_text) for the dialog nav bar."""
        sols = _state["solutions"]
        if not sols:
            return (0, 0, "Run Preview to compute layouts")
        idx = _state["idx"]
        sol = sols[idx]
        cfg = _state["cfg"] or {}
        am  = sol.get("minus_achieved") or "—"
        ap  = sol.get("plus_achieved")  or "—"
        tm  = cfg.get("pack_minus_target", "?")
        tp  = cfg.get("pack_plus_target",  "?")
        ms  = "✓" if am == tm else f"{tm} → {am}"
        ps  = "✓" if ap == tp else f"{tp} → {ap}"
        parts = [f"PACK−: {ms}", f"PACK+: {ps}"]
        if sol.get("arch_info"):
            parts.append(sol["arch_info"])
        else:
            parts.append("⚠ adaptive result — architecture not honored")
        if sol.get("jumps"):
            parts.append(f"Jumps: {len(sol['jumps'])}")
        if sol.get("failure"):
            parts.append(f"⚠ {FAILURE_MESSAGES.get(sol['failure'], sol['failure'])}")
        return (idx + 1, len(sols), "   ".join(parts))

    # ── Cleanup on Cancel ─────────────────────────────────────────────────

    def _cleanup() -> None:
        last = _state["last_root"]
        if last:
            _delete_tree(doc, last[0])
            doc.recompute()

    cfg = get_user_settings(
        load_defaults(),
        preview_fn=_draw,
        cleanup_fn=_cleanup,
        prev_fn=_prev,
        next_fn=_next,
        nav_info_fn=_nav_info,
    )
    if cfg is None:
        _cleanup()
        print("BatteryPackLayoutTool: cancelled.")
        return

    # ── Busbar catalog validation ────────────────────────────────────────
    try:
        from cellpacker.busbar_catalog import load_catalog, validate_fit
        catalog = load_catalog()
        fit = validate_fit(catalog, cfg["cell_diameter"])
        if fit != "ok":
            from PySide2 import QtWidgets
            if fit == "no_catalog_match":
                msg = (
                    f"No busbars in the catalog are compatible with "
                    f"{cfg['cell_diameter']:.1f} mm cells.\n\n"
                    "You can still generate the pack without busbars, or add a "
                    "compatible entry to cellpacker/busbars.json and re-run."
                )
                btns = QtWidgets.QMessageBox.Ok | QtWidgets.QMessageBox.Cancel
            else:  # none_in_stock
                msg = (
                    f"The catalog has busbars for {cfg['cell_diameter']:.1f} mm cells "
                    "but none are marked in_stock.\n\n"
                    "Mark the strips you have available in cellpacker/busbars.json, "
                    "or continue anyway to generate the pack without a busbar selection."
                )
                btns = QtWidgets.QMessageBox.Ok | QtWidgets.QMessageBox.Cancel

            reply = QtWidgets.QMessageBox.warning(
                None, "Busbar catalog", msg, btns,
            )
            if reply == QtWidgets.QMessageBox.Cancel:
                _cleanup()
                print("BatteryPackLayoutTool: cancelled (no matching busbar).")
                return
    except Exception as exc:
        print(f"BatteryPackLayoutTool: busbar catalog check skipped — {exc}")

    # On OK: re-render whichever solution the user navigated to (no recompute).
    # If the user never clicked Preview, do a full compute+render now.
    if _state["solutions"]:
        _render(_state["cfg"] or {**cfg, **build_layers(cfg)},
                _state["solutions"][_state["idx"]])
    else:
        _draw(cfg)
    print("BatteryPackLayoutTool: done.")


# Entry point when executed as a FreeCAD macro
run()
